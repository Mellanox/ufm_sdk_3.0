MELLANOX-SMI-MIB DEFINITIONS ::= BEGIN

IMPORTS
	OBJECT-IDENTITY, MODULE-IDENTITY, enterprises
		FROM SNMPv2-SMI;

-- Mellanox-SMI-MIB
-- 

mellanox MODULE-IDENTITY
	LAST-UPDATED "202108120000Z"
	ORGANIZATION 
		"Mellanox Technologies, Inc."
	CONTACT-INFO 
		"
		Mellanox Technologies, Inc.
		350 Oakmead Parkway, Suite 100
		Sunnyvale, CA 94085
		Tel: 408-970-3400
		Fax: 408-970-3403
		E-mail: info@mellanox.com
		        "
	DESCRIPTION 
		"Mellanox Vendor MIB."

	REVISION "202108120000Z"
	DESCRIPTION 
		"Added MSTP MIB entry"

	REVISION "201905190000Z"
	DESCRIPTION 
		"Added WJH MIB entry"

::= { enterprises 33049 }


mellanoxProducts  OBJECT-IDENTITY
	STATUS     current
	DESCRIPTION 
		"mellanoxProducts is used for sysObjectID values to be assigned. Values are defined in MELLANOX-PRODUCTS-MIB."
	::= { mellanox 1 }

mellanoxIfVPI  OBJECT-IDENTITY
	STATUS     current
	DESCRIPTION 
		"mellanoxifVPI MIB is used for extendedinterface info for VPI (Ethernet and IB) interfaces."
	::= { mellanox 3 }

mellanoxUFMTrap  OBJECT-IDENTITY
	STATUS     current
	DESCRIPTION 
		"mellanoxUFMTrap MIB defines the list of SNMP traps being generated by Mellanox Unified Fabric Manager (UFM)."
	::= { mellanox 4 }

-- Entity MIB extensions

mellanoxEntity  OBJECT-IDENTITY 	
	STATUS     current
	DESCRIPTION 
		"mellanoxEntity defines an extenstion to Entity MIB."
	::= { mellanox 5 }

-- Entity State MIB extension

mellanoxEntState  OBJECT-IDENTITY
     STATUS     current
     DESCRIPTION
           "mellanoxEntState MIB defines Entity State functionality."
     ::= { mellanox 7 } 
	
-- Mellanox DCB Traps MIB

mellanoxDCBTraps  OBJECT-IDENTITY
	STATUS     current
	DESCRIPTION 
		"mellanoxDCBTraps MIB defines DCB traps functionality."
	::= { mellanox 8 }

-- Mellanox MSTP Traps MIB

mellanoxMstp  OBJECT-IDENTITY
	STATUS     current
	DESCRIPTION 
		"mellanoxMstp MIB defines MSTP related functionality."
	::= { mellanox 9 }
	
-- Mellanox Power Cycle MIB

mellanoxPowerCycle  OBJECT-IDENTITY
	STATUS     current
	DESCRIPTION 
		"mellanoxPowerCycle MIB defines power cycle related functionality."
	::= { mellanox 10 }

-- Mellanox SW Update MIB

mellanoxSWUpdate   OBJECT-IDENTITY
	STATUS     current
	DESCRIPTION 
		"mellanoxSWUpdate MIB defines SW image related functionality."
	::= { mellanox 11 }

-- Mellanox Configuration DB MIB

mellanoxConfigDB   OBJECT-IDENTITY
	STATUS     current
	DESCRIPTION 
		"mellanoxConfigDB MIB defines configuration related functionality."
	::= { mellanox 12 }

-- Mellanox XSTP MIB
mellanoxXstp       OBJECT-IDENTITY
	STATUS     current
	DESCRIPTION 
		"mellanoxXstp MIB defines MSTP/PVRST+ related functionality."
	::= { mellanox 13 }

-- Mellanox VRF MIB
mellanoxVRF       OBJECT-IDENTITY
	STATUS     current
	DESCRIPTION 
		"mellanoxVRF MIB defines VRF related functionality."
	::= { mellanox 14 }
	
-- Mellanox QoS MIB
mellanoxQoS       OBJECT-IDENTITY
	STATUS     current
	DESCRIPTION 
		"mellanoxQoS MIB defines QoS related functionality."
	::= { mellanox 15 }

-- Mellanox WJH MIB
mellanoxWJH       OBJECT-IDENTITY
	STATUS     current
	DESCRIPTION 
		"mellanoxWJH MIB defines 'What Just Happened?' related functionality."
	::= { mellanox 16 }

END
